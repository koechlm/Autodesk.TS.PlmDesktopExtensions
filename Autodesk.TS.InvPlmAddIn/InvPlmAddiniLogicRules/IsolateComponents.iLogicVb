AddReference "Adsk.Ts.VaultUtils.dll"

Public Sub main

	Dim mPartnumbers As String() = RuleArguments("PartNumbers")
	Dim mDoc As Inventor.Document = ThisApplication.ActiveDocument

	If mPartnumbers Is Nothing Then
		Logger.Error("Rule exits due to missing rule argument 'Partnumber'")
		AdskTsVaultUtils.Messages.ShowError("Rule exits due to missing rule argument [Partnumbers].", "iLogic-Vault")
		Exit Sub
	End If

	'PartNumbers may be handed as latest element of an instance or part number path (user selected proxies)
	Dim mTemp As New List(Of String)
	For Each mNum In mPartnumbers
		If mNum.Split("|").Length > 1
			mTemp.Add(mNum.Split("|").LastOrDefault().Split(":").FirstOrDefault())
		Else
			mTemp.Add(mNum)
		End If
	Next
	mPartnumbers = mTemp.ToArray()

	'differentiate selection of bodies in multi-body part files and occurrences in assemblies
	'Region assembly
	If (ThisApplication.ActiveDocumentType = Inventor.DocumentTypeEnum.kAssemblyDocumentObject) Then
		Dim mAsmDoc As AssemblyDocument = mDoc

		'assembly occurrences are cached in iLogic SharedVariable storage on document open
		If (Not SharedVariable.Exists(mDoc.FullDocumentName)) Then
			Logger.Error("SharedVariable for Cache Object not found. Run the PLMInventor Rule 'OnDocumentOpen manually if you are debugging.'")
			Return
		End If
		Dim occurenceCache As Dictionary(Of String, List(Of ComponentOccurrence)) = SharedVariable(mDoc.FullDocumentName)

		' clear current isolate view
		Dim ctrlDef = ThisApplication.CommandManager.ControlDefinitions.Item("AssemblyIsolateUndoCmd")
		While ctrlDef.Enabled
			ctrlDef.Execute
		End While

		'Perform Selection
		mAsmDoc.SelectSet.Clear()
		For Each s In occurenceCache.Where(Function(x)
			Return mPartnumbers.Contains(x.Key)
			End Function )
			Logger.Info("Select occurences for partnumber " & s.Key & "; Count: " & s.Value.Count)
			Dim occ As ComponentOccurrence
			For Each occ In s.Value
				mAsmDoc.SelectSet.Select(occ)
			Next
		Next

		ThisApplication.CommandManager.ControlDefinitions.Item("AssemblyIsolateCmd").Execute

	End If 'region assembly

	' region for Multi-Body part components
	If (ThisApplication.ActiveDocumentType = Inventor.DocumentTypeEnum.kPartDocumentObject) Then

		Dim mPrtDoc As PartDocument = mDoc
		Dim mCompDef As Inventor.PartComponentDefinition = mPrtDoc.ComponentDefinition
		Dim mBodyCache As Dictionary(Of String, List(Of SurfaceBody))

		If mCompDef.SurfaceBodies.Count > 1 Then
			'get the cache for faster selection or create it on first time run
			If SharedVariable.Exists(mDoc.FullDocumentName) Then
				mBodyCache = SharedVariable(mDoc.FullDocumentName)
			Else
				mBodyCache = New Dictionary(Of String, List(Of SurfaceBody))()
				For Each mBody As SurfaceBody In mCompDef.SurfaceBodies
					Dim mBodyPartNumber As String = mExtractPartNumFromBodyName(mBody.Name)
					If mBodyPartNumber <> Nothing Then
						If mBodyCache.ContainsKey(mBodyPartNumber) Then
							'there is a list of bodies with the same partnumber
							mBodyCache(mBodyPartNumber).Add(mBody)
						Else
							'create a new list of bodies for this partnumber
							mBodyList = New List(Of Inventor.SurfaceBody)
							mBodyList.Add(mBody)
							mBodyCache.Add(mBodyPartNumber, mBodyList)
						End If
					End If 'partnumber exists
				Next
				'create a shared variable for the cache
				SharedVariable(mDoc.FullDocumentName) = mBodyCache
			End If

			'Perform Selection
			mPrtDoc.SelectSet.Clear()
			For Each mBody As SurfaceBody In mCompDef.SurfaceBodies
				Dim mBodyPartNumber As String = mExtractPartNumFromBodyName(mBody.Name)
				'emulate an "isolate" command: hide each body, to unhide the selected ones only
				mBody.Visible = False
				For Each s In mBodyCache.Where(Function(x)
					Return mPartnumbers.Contains(x.Key)
					End Function )
					'Logger.Info("Select bodies for partnumber " & s.Key & "; Count: " & s.Value.Count)
					For Each body As SurfaceBody In s.Value
						mPrtDoc.SelectSet.Select(body)
						body.Visible = True
					Next
				Next
			Next

		End If 'multi-body count > 1

	End If
	' end region Mulit-Body selection


End Sub

Private Function mExtractPartNumFromBodyName(Name As String)
	Dim mNameSubStrings As String() = Name.Split("_")
	'the name convention is: Pos_'CAD'_Number_Title_LxBxH
	If mNameSubStrings.Length >= 3
		Return mNameSubStrings(1) + "_" + mNameSubStrings(2)
	End If
	Return Nothing
End Function
